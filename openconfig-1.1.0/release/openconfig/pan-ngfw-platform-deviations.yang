module pan-ngfw-platform-deviations {
  namespace "http://github.com/PaloAltoNetworks/yang/openconfig-1.0.0/release/openconfig/pan-ngfw-platform-deviations.yang";

  prefix "pan-ngfw-platform-deviations";

  import openconfig-platform { prefix "oc-platform"; }

  organization
    "Palo Alto Networks";

  revision 2021-03-16 {
    description
      "Initial deviations file.";
    reference "0.0.1";
  }

  deviation "/oc-platform:components/oc-platform:component/oc-platform:state/oc-platform:location" {
    deviate not-supported;
  }

  deviation "/oc-platform:components/oc-platform:component/oc-platform:state/oc-platform:mfg-date" {
    deviate not-supported;
  }

  deviation "/oc-platform:components/oc-platform:component/oc-platform:state/oc-platform:part-no" {
    deviate not-supported;
  }

  deviation "/oc-platform:components/oc-platform:component/oc-platform:state/oc-platform:oper-status" {
    deviate not-supported;
  }

  deviation "/oc-platform:components/oc-platform:component/oc-platform:state/oc-platform:temperature/oc-platform:avg" {
    deviate not-supported;
  }

  deviation "/oc-platform:components/oc-platform:component/oc-platform:state/oc-platform:temperature/oc-platform:interval" {
    deviate not-supported;
  }

  deviation "/oc-platform:components/oc-platform:component/oc-platform:state/oc-platform:temperature/oc-platform:min-time" {
    deviate not-supported;
  }

  deviation "/oc-platform:components/oc-platform:component/oc-platform:state/oc-platform:temperature/oc-platform:max-time" {
    deviate not-supported;
  }

  deviation "/oc-platform:components/oc-platform:component/oc-platform:state/oc-platform:temperature/oc-platform:alarm-threshold" {
    deviate not-supported;
  }

  deviation "/oc-platform:components/oc-platform:component/oc-platform:state/oc-platform:temperature/oc-platform:alarm-severity" {
    deviate not-supported;
  }

  deviation "/oc-platform:components/oc-platform:component/oc-platform:state/oc-platform:allocated-power" {
    deviate not-supported;
  }

  deviation "/oc-platform:components/oc-platform:component/oc-platform:state/oc-platform:used-power" {
    deviate not-supported;
  }

  deviation "/oc-platform:components/oc-platform:component/oc-platform:fan" {
    deviate not-supported;
  }

  deviation "/oc-platform:components/oc-platform:component/oc-platform:fabric" {
    deviate not-supported;
  }

  deviation "/oc-platform:components/oc-platform:component/oc-platform:port" {
    deviate not-supported;
  }

  deviation "/oc-platform:components/oc-platform:component/oc-platform:cpu" {
    deviate not-supported;
  }

  deviation "/oc-platform:components/oc-platform:component/oc-platform:power-supply" {
    deviate not-supported;
  }

  deviation "/oc-platform:components/oc-platform:component/oc-platform:integrated-circuit" {
    deviate not-supported;
  }

  deviation "/oc-platform:components/oc-platform:component/oc-platform:backplane" {
    deviate not-supported;
  }
}
