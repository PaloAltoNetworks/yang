module pan-ngfw-system-deviations {
  namespace "http://github.com/PaloAltoNetworks/yang/openconfig-1.0.0/release/openconfig/pan-ngfw-system-deviations.yang";

  prefix "pan-ngfw-system-deviations";

  import openconfig-system { prefix "oc-sys"; }

  organization
    "Palo Alto Networks";

  revision 2021-01-12 {
    description
      "Initial deviations file.";
    reference "0.0.1";
  }

  deviation "/oc-sys:system/oc-sys:ntp/oc-sys:config/oc-sys:enabled" {
    deviate not-supported;
  }

  deviation "/oc-sys:system/oc-sys:ntp/oc-sys:state/oc-sys:enabled" {
    deviate not-supported;
  }

  deviation "/oc-sys:system/oc-sys:ntp/oc-sys:config/oc-sys:ntp-source-address" {
    deviate not-supported;
  }

  deviation "/oc-sys:system/oc-sys:ntp/oc-sys:state/oc-sys:ntp-source-address" {
    deviate not-supported;
  }

  deviation "/oc-sys:system/oc-sys:ntp/oc-sys:servers/oc-sys:server/oc-sys:config/oc-sys:port" {
    deviate not-supported;
  }

  deviation "/oc-sys:system/oc-sys:ntp/oc-sys:servers/oc-sys:server/oc-sys:state/oc-sys:port" {
    deviate not-supported;
  }

  deviation "/oc-sys:system/oc-sys:ntp/oc-sys:servers/oc-sys:server/oc-sys:config/oc-sys:iburst" {
    deviate not-supported;
  }

  deviation "/oc-sys:system/oc-sys:ntp/oc-sys:servers/oc-sys:server/oc-sys:state/oc-sys:iburst" {
    deviate not-supported;
  }

  deviation "/oc-sys:system/oc-sys:ntp/oc-sys:servers/oc-sys:server/oc-sys:config/oc-sys:version" {
    deviate not-supported;
  }

  deviation "/oc-sys:system/oc-sys:ntp/oc-sys:servers/oc-sys:server/oc-sys:state/oc-sys:version" {
    deviate not-supported;
  }

  deviation "/oc-sys:system/oc-sys:ntp/oc-sys:state/oc-sys:auth-mismatch" {
    deviate not-supported;
  }

  deviation "/oc-sys:system/oc-sys:config/oc-sys:motd-banner" {
    deviate not-supported;
  }

  deviation "/oc-sys:system/oc-sys:state/oc-sys:motd-banner" {
    deviate not-supported;
  }

  deviation "/oc-sys:system/oc-sys:state/oc-sys:boot-time" {
    deviate not-supported;
  }

  deviation "/oc-sys:system/oc-sys:dns/oc-sys:config/oc-sys:search" {
    deviate not-supported;
  }

  deviation "/oc-sys:system/oc-sys:dns/oc-sys:state/oc-sys:search" {
    deviate not-supported;
  }

  deviation "/oc-sys:system/oc-sys:dns/oc-sys:host-entries" {
    deviate not-supported;
  }

  deviation "/oc-sys:system/oc-sys:grpc-server" {
    deviate not-supported;
  }

  deviation "/oc-sys:system/oc-sys:ssh-server" {
    deviate not-supported;
  }

  deviation "/oc-sys:system/oc-sys:telnet-server" {
    deviate not-supported;
  }

  deviation "/oc-sys:system/oc-sys:alarms" {
    deviate not-supported;
  }

  deviation "/oc-sys:system/oc-sys:messages" {
    deviate not-supported;
  }

  deviation "/oc-sys:system/oc-sys:logging" {
    deviate not-supported;
  }

  deviation "/oc-sys:system/oc-sys:aaa" {
    deviate not-supported;
  }

  deviation "/oc-sys:system/oc-sys:license/oc-sys:licenses/oc-sys:license/oc-sys:config/oc-sys:license-data" {
    deviate not-supported;
  }

  deviation "/oc-sys:system/oc-sys:license/oc-sys:licenses/oc-sys:license/oc-sys:state/oc-sys:license-data" {
    deviate not-supported;
  }

  deviation "/oc-sys:system/oc-sys:license/oc-sys:licenses/oc-sys:license/oc-sys:config/oc-sys:license-id" {
    deviate add {
      config false;
    }
  }

  deviation "/oc-sys:system/oc-sys:license/oc-sys:licenses/oc-sys:license/oc-sys:config/oc-sys:active" {
    deviate not-supported;
  }

  deviation "/oc-sys:system/oc-sys:cpus/oc-sys:cpu/oc-sys:state/oc-sys:total/oc-sys:avg" {
    deviate not-supported;
  }

  deviation "/oc-sys:system/oc-sys:cpus/oc-sys:cpu/oc-sys:state/oc-sys:total/oc-sys:min" {
    deviate not-supported;
  }

  deviation "/oc-sys:system/oc-sys:cpus/oc-sys:cpu/oc-sys:state/oc-sys:total/oc-sys:max" {
    deviate not-supported;
  }

  deviation "/oc-sys:system/oc-sys:cpus/oc-sys:cpu/oc-sys:state/oc-sys:total/oc-sys:interval" {
    deviate not-supported;
  }

  deviation "/oc-sys:system/oc-sys:cpus/oc-sys:cpu/oc-sys:state/oc-sys:total/oc-sys:min-time" {
    deviate not-supported;
  }

  deviation "/oc-sys:system/oc-sys:cpus/oc-sys:cpu/oc-sys:state/oc-sys:total/oc-sys:max-time" {
    deviate not-supported;
  }

  deviation "/oc-sys:system/oc-sys:cpus/oc-sys:cpu/oc-sys:state/oc-sys:user/oc-sys:avg" {
    deviate not-supported;
  }

  deviation "/oc-sys:system/oc-sys:cpus/oc-sys:cpu/oc-sys:state/oc-sys:user/oc-sys:min" {
    deviate not-supported;
  }

  deviation "/oc-sys:system/oc-sys:cpus/oc-sys:cpu/oc-sys:state/oc-sys:user/oc-sys:max" {
    deviate not-supported;
  }

  deviation "/oc-sys:system/oc-sys:cpus/oc-sys:cpu/oc-sys:state/oc-sys:user/oc-sys:interval" {
    deviate not-supported;
  }

  deviation "/oc-sys:system/oc-sys:cpus/oc-sys:cpu/oc-sys:state/oc-sys:user/oc-sys:min-time" {
    deviate not-supported;
  }

  deviation "/oc-sys:system/oc-sys:cpus/oc-sys:cpu/oc-sys:state/oc-sys:user/oc-sys:max-time" {
    deviate not-supported;
  }

  deviation "/oc-sys:system/oc-sys:cpus/oc-sys:cpu/oc-sys:state/oc-sys:kernel/oc-sys:avg" {
    deviate not-supported;
  }

  deviation "/oc-sys:system/oc-sys:cpus/oc-sys:cpu/oc-sys:state/oc-sys:kernel/oc-sys:min" {
    deviate not-supported;
  }

  deviation "/oc-sys:system/oc-sys:cpus/oc-sys:cpu/oc-sys:state/oc-sys:kernel/oc-sys:max" {
    deviate not-supported;
  }

  deviation "/oc-sys:system/oc-sys:cpus/oc-sys:cpu/oc-sys:state/oc-sys:kernel/oc-sys:interval" {
    deviate not-supported;
  }

  deviation "/oc-sys:system/oc-sys:cpus/oc-sys:cpu/oc-sys:state/oc-sys:kernel/oc-sys:min-time" {
    deviate not-supported;
  }

  deviation "/oc-sys:system/oc-sys:cpus/oc-sys:cpu/oc-sys:state/oc-sys:kernel/oc-sys:max-time" {
    deviate not-supported;
  }

  deviation "/oc-sys:system/oc-sys:cpus/oc-sys:cpu/oc-sys:state/oc-sys:nice/oc-sys:avg" {
    deviate not-supported;
  }

  deviation "/oc-sys:system/oc-sys:cpus/oc-sys:cpu/oc-sys:state/oc-sys:nice/oc-sys:min" {
    deviate not-supported;
  }

  deviation "/oc-sys:system/oc-sys:cpus/oc-sys:cpu/oc-sys:state/oc-sys:nice/oc-sys:max" {
    deviate not-supported;
  }

  deviation "/oc-sys:system/oc-sys:cpus/oc-sys:cpu/oc-sys:state/oc-sys:nice/oc-sys:interval" {
    deviate not-supported;
  }

  deviation "/oc-sys:system/oc-sys:cpus/oc-sys:cpu/oc-sys:state/oc-sys:nice/oc-sys:min-time" {
    deviate not-supported;
  }

  deviation "/oc-sys:system/oc-sys:cpus/oc-sys:cpu/oc-sys:state/oc-sys:nice/oc-sys:max-time" {
    deviate not-supported;
  }

  deviation "/oc-sys:system/oc-sys:cpus/oc-sys:cpu/oc-sys:state/oc-sys:idle/oc-sys:avg" {
    deviate not-supported;
  }

  deviation "/oc-sys:system/oc-sys:cpus/oc-sys:cpu/oc-sys:state/oc-sys:idle/oc-sys:min" {
    deviate not-supported;
  }

  deviation "/oc-sys:system/oc-sys:cpus/oc-sys:cpu/oc-sys:state/oc-sys:idle/oc-sys:max" {
    deviate not-supported;
  }

  deviation "/oc-sys:system/oc-sys:cpus/oc-sys:cpu/oc-sys:state/oc-sys:idle/oc-sys:interval" {
    deviate not-supported;
  }

  deviation "/oc-sys:system/oc-sys:cpus/oc-sys:cpu/oc-sys:state/oc-sys:idle/oc-sys:min-time" {
    deviate not-supported;
  }

  deviation "/oc-sys:system/oc-sys:cpus/oc-sys:cpu/oc-sys:state/oc-sys:idle/oc-sys:max-time" {
    deviate not-supported;
  }

  deviation "/oc-sys:system/oc-sys:cpus/oc-sys:cpu/oc-sys:state/oc-sys:wait/oc-sys:avg" {
    deviate not-supported;
  }

  deviation "/oc-sys:system/oc-sys:cpus/oc-sys:cpu/oc-sys:state/oc-sys:wait/oc-sys:min" {
    deviate not-supported;
  }

  deviation "/oc-sys:system/oc-sys:cpus/oc-sys:cpu/oc-sys:state/oc-sys:wait/oc-sys:max" {
    deviate not-supported;
  }

  deviation "/oc-sys:system/oc-sys:cpus/oc-sys:cpu/oc-sys:state/oc-sys:wait/oc-sys:interval" {
    deviate not-supported;
  }

  deviation "/oc-sys:system/oc-sys:cpus/oc-sys:cpu/oc-sys:state/oc-sys:wait/oc-sys:min-time" {
    deviate not-supported;
  }

  deviation "/oc-sys:system/oc-sys:cpus/oc-sys:cpu/oc-sys:state/oc-sys:wait/oc-sys:max-time" {
    deviate not-supported;
  }

  deviation "/oc-sys:system/oc-sys:cpus/oc-sys:cpu/oc-sys:state/oc-sys:hardware-interrupt/oc-sys:avg" {
    deviate not-supported;
  }

  deviation "/oc-sys:system/oc-sys:cpus/oc-sys:cpu/oc-sys:state/oc-sys:hardware-interrupt/oc-sys:min" {
    deviate not-supported;
  }

  deviation "/oc-sys:system/oc-sys:cpus/oc-sys:cpu/oc-sys:state/oc-sys:hardware-interrupt/oc-sys:max" {
    deviate not-supported;
  }

  deviation "/oc-sys:system/oc-sys:cpus/oc-sys:cpu/oc-sys:state/oc-sys:hardware-interrupt/oc-sys:interval" {
    deviate not-supported;
  }

  deviation "/oc-sys:system/oc-sys:cpus/oc-sys:cpu/oc-sys:state/oc-sys:hardware-interrupt/oc-sys:min-time" {
    deviate not-supported;
  }

  deviation "/oc-sys:system/oc-sys:cpus/oc-sys:cpu/oc-sys:state/oc-sys:hardware-interrupt/oc-sys:max-time" {
    deviate not-supported;
  }

   deviation "/oc-sys:system/oc-sys:cpus/oc-sys:cpu/oc-sys:state/oc-sys:software-interrupt/oc-sys:avg" {
    deviate not-supported;
  }

  deviation "/oc-sys:system/oc-sys:cpus/oc-sys:cpu/oc-sys:state/oc-sys:software-interrupt/oc-sys:min" {
    deviate not-supported;
  }

  deviation "/oc-sys:system/oc-sys:cpus/oc-sys:cpu/oc-sys:state/oc-sys:software-interrupt/oc-sys:max" {
    deviate not-supported;
  }

  deviation "/oc-sys:system/oc-sys:cpus/oc-sys:cpu/oc-sys:state/oc-sys:software-interrupt/oc-sys:interval" {
    deviate not-supported;
  }

  deviation "/oc-sys:system/oc-sys:cpus/oc-sys:cpu/oc-sys:state/oc-sys:software-interrupt/oc-sys:min-time" {
    deviate not-supported;
  }

  deviation "/oc-sys:system/oc-sys:cpus/oc-sys:cpu/oc-sys:state/oc-sys:software-interrupt/oc-sys:max-time" {
    deviate not-supported;
  }

  deviation "/oc-sys:system/oc-sys:processes/oc-sys:process/oc-sys:state/oc-sys:args" {
    deviate not-supported;
  }

  deviation "/oc-sys:system/oc-sys:processes/oc-sys:process/oc-sys:state/oc-sys:start-time" {
    deviate not-supported;
  }

  typedef process-cpu-utilization {
    type uint16;
    description
        "The percentage of CPU that is being used by the process.
         The percentange could be higher than 100 on multicore processes";
  }

  deviation "/oc-sys:system/oc-sys:processes/oc-sys:process/oc-sys:state/oc-sys:cpu-utilization" {
    deviate replace {
      type process-cpu-utilization;
    }
  }
}
