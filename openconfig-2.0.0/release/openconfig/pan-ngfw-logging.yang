module pan-ngfw-logging {

    yang-version "1";

    namespace "http://github.com/PaloAltoNetworks/yang/openconfig-1.0.0/release/openconfig/pan/pan-ngfw-logging.yang";

    prefix "pan-ngfw-st-logging";

    import pan-ngfw-st-base {
        prefix pan-ngfw-st-base;
    }

    // "pan/logging/query/custom[type=system][direction=fwd][max_logs=2][period=last-24-hrs]"
    // "pan/logging/query/custom[type=system][direction=fwd][max_logs=2][query_str=\'severity eq critical\'][from_time=t1][to_time=t2]"
    // "pan/logging/query/custom[type=system][direction=fwd][max_logs=2][query_str=\'severity eq critical\'][from_time=\'2023/04/20@00:11:29\'][to_time=\'2023/04/20@01:12:29\']"
    // "pan/logging/query/custom[full_query=-t system -n 5]"
    // "pan/logging/query/predefined/system_logs_vpn_and_dpd_15_min"
    // With all the commands optional data_push_url can be passed to upload the results to the URL provided here. e.g. "pan/logging/query/custom[type=system][direction=fwd][max_logs=2][period=last-24-hrs][data_push_url=<URL>]"

    //dial_in with data_push URL, if there is a file/output for the comamnd, it is always uploaded, no size check is performed

//    Predefined path: system_logs_vpn_and_dpd_15_min
//    Query: pan_logquery  -t system -i bwd -n 1500 -e last-15-minutes -q \'subtype eq vpn\' | grep \'status-up\|status-down\|DPD\'
    
//    Description: system.log
//    Rationale: Collects system logs generated by the device over the previous six hours. These logs are written by various PAN-OS subsystems (URL filtering, WildFire, etc), and usually include messages about events that occured in the subsystem (a network connection was made, a cert was not successfully installed, and so forth). Each log line includes timestamp information and the device hostname where the log was generated. Log lines will also frequently include IP addresses, hostnames, and ports with which the device interacted over the network.
//    Predefined path: system_log
//   Query: pan_logquery -t system -n 1500 -i bwd -q \'(severity eq critical) or (severity eq high)\' -e last-hour
    
//   Description: Identifies the percentage of the network traffic seen by the firewall that is either one-way or asymmetric (one direction of the traffic flow is not being seen by the firewall).
//   Rationale: If we are not able to get the two sides of traffic we cannot inspect best as we do not have whole data. What we should know is how many customers have such traffic ? and in what scenarios or Apps they need such traffic ? How can we get such traffic fully inspected.
//   Predefined path: percentage_of_traffic_that_is_one_way_or_asymmetric
//   Query: pan_logquery  -t traffic -n 5000 -e last-24-hrs -q \'( ( (pkts_received eq 0) and (pkts_sent geq 3) ) or ( (pkts_sent eq 0) and (pkts_received geq 3) ) ) and (app neq ping) and (app neq dns)\'
    
//    Description: Raven, and DNS Signature threat logs
//    Rationale: Contains threat logs where the threat category was related to DNS.
//    Predefined path: raven_and_DNS_signature_threat_logs
//    Query: pan_logquery  -t threat -n 5000 -e last-24-hrs -q \'(category-of-threatid eq dns) or (category-of-threatid eq dns-wildfire) or (category-of-threatid eq autogen)\'
    
//    Description: PAN-DNS related logs
//    Rationale: Contains threat logs where the threat category is dns-cloud. That is, threat logs based on information retrieved from Palo Alto Networks Cloud-Delivered DNS signature service.
//    Predefined path: PAN_DNS_related_logs
//    Query: pan_logquery  -t threat -n 5000 -e last-24-hrs -q \'(category-of-threatid eq dns-cloud)\'
    
//    Description: Config Log activity including commit and its timestamp
//    Rationale: Shows the configuration changes made to the device over the previous collection interval. These log records identify the changes made to the device, the person who made the change, plus a time stamp for when each configuration change was made. 
//    Predefined path: config_log
//    Query: pan_logquery  -t config -n 1500 -i bwd -e last-24-hrs -o domain,receive_time,serial,type,subtype,config_ver,time_generated,host,vsys,cmd,admin,client,result,path,seqno,actionflags,dg_hier_level_1,dg_hier_level_2,dg_hier_level_3,dg_hier_level_4,vsys_name,device_name,dg_id,comment,tpl_id,high_res_timestamp,before-change-detail,after-change-detail,full-path
    
//    Description: percentage of SaaS applications that has malware
//    Rationale: Identifies the percentage of SaaS application traffic that the firewall is categorizing as threatening in some way. For example, because the traffic appears to be generated by a virus or spyware.
//    Predefined path: percentage_of_SaaS_applications_that_has_malware
//    Query: pan_logquery  -t threat -n 5000 -e last-24-hrs -q \'(characteristic-of-app eq is-saas) and ((subtype eq spyware) or (subtype eq virus) or (subtype eq vulnerability) or (subtype eq wildfire-virus))\'
    
//    Description: URL Malware blocks
//    Rationale: Contains URL logs of traffic that was blocked because it was categorized as malware. This helps identify how much of the device's traffic is being blocked as malware.
//    Predefined path: URL_malware_blocks
//    Query: pan_logquery  -t urlsum -n 5000 -e last-24-hrs -q \'( (category eq malware) or (category eq command-and-control) or (category eq phishing) ) and ( (action eq block) or (action eq deny) or (action eq drop) or (action eq reset-both) or (action eq block-url) )\'
    
//    Description: URL C2 blocks
//    Rationale: Contains URL logs of traffic that was blocked because it was categorized as malware command and control traffic. This helps identify how much of the device's traffic is being blocked as command and control.
//    Predefined path: URL_C2_blocks
//    Query: pan_logquery  -t urlsum -n 5000 -e last-24-hrs -q \'( (category eq malware) or (category eq command-and-control) or (category eq phishing) ) and ( (action eq block) or (action eq deny) or (action eq drop) or (action eq reset-both) or (action eq block-url) )\'
    
//    Description: URL Phishing Blocks
//    Rationale: Contains URL logs of traffic that was blocked because it was categorized as phishing. This helps identify how much of the device's traffic is being blocked as phishing.
//    Predefined path: URL_phishing_blocks
//    Query: pan_logquery  -t urlsum -n 5000 -e last-24-hrs -q \'( (category eq malware) or (category eq command-and-control) or (category eq phishing) ) and ( (action eq block) or (action eq deny) or (action eq drop) or (action eq reset-both) or (action eq block-url) )\'
    
//    Description: Wildfire Detections
//    Rationale: Contains threat logs where the threat type is *wildfire-virus*. This means that the traffic has been confirmed by WildFire to have been generated by a virus.
//    Predefined path: wildfire_detections
//    Query: pan_logquery  -t threat -n 5000 -e last-24-hrs -q \'(threat-type eq wildfire-virus)\'
    
//    Description: Identify Credential Phishing has occurred.
//    Rationale: Collects information on the firewall's credential theft policy usage. Examines URL logs for traffic where credentials are presented, and collects information about the username, destination zone, the action the firewall took in response to the traffic, the application in use, and the URL used for the traffic. Also identifies the security and profiles used by the firewall to determine the action that it took for this traffic.
//    Predefined path: credential_theft
//    Query: pan_logquery  -t url -n 5000 -e last-24-hrs -q \'( flags has credential-detected )\'
    
//    Description: This shows how many threats have been allowed in the network. This data should educate customers on threat visibility.
//    Rationale: Identifies threatening network traffic the firewall failed to block. Collects threat summary log records where the threat type was virus, vulnerability, wildfire-virus, or spyware; the threat severity was greater than or equal to medium; and the firewall's action was only to raise an alert.
//    Predefined path: threats_permitted
//    Query: pan_logquery  -t thsum -q \'(action eq alert) and (severity geq medium) and ( (threat-type eq virus) or (threat-type eq vulnerability) or (threat-type eq wildfire-virus) or (threat-type eq spyware) )\' -n 5000 -e last-24-hrs
    
//    Predefined path: system_logs_vpn_and_dpd_5_min
//    Query: pan_logquery  -t system -i bwd -n 1500 -e last-5-minutes -q \'subtype eq vpn\' | grep \'status-up\|status-down\|DPD\'
    
//    Description: Collects information from correlated event logs that were generated by the device over the previous six hours. This information includes the correlated object ID and name that was matched.
//    Rationale: Existing telemetry collection for Threat Research
//    Predefined path: corr_object_events
//    Query: pan_logquery -t corr -n 1500 -i bwd -o object_id,version,object_name -e last-24-hrs
    
//    Description: Retrieves information from correlated event logs that were generated by the device over the previous six hours. Details include the object ID and name that was matched, as well as the device serial number where the log was generated.
//    Rationale: Existing telemetry collection for Threat Research
//    Predefined path: corr_detailed_telemetry
//    Query: pan_logquery -t corr -n 1500 -i bwd -o object_id,version,object_name,serial,match_oid -e last-24-hrs ";

    oc-ext:openconfig-version "1.0.0";

    organization "Palo Alto Networks";

    description
        "Streaming-Telemetry Logging";


    revision "2022-07-12" {
        description "Initial version";
        reference "1.0.0";
    }

    grouping config-type {
        leaf query_str {
            type string;
        }
        leaf type {
            type string;
        }
        leaf direction {
            type string;
        }
        leaf from_time {
            type string;
        }
        leaf to_time {
            type string;
        }
        leaf period {
            type string;
        }
        leaf full_query {
            type string;
        }
        leaf data_push_url {
            type string;
        }
        leaf max_logs {
            type int32;
        }
    }

    augment "/pan-ngfw-st-base:pan" {

        container logging {
            description "Top level container for Streaming Telemetry logging";

            container query {
                description "This contains custom queries";

                list custom {
                    key "query_str max_logs direction type from_time to_time period full_query data_push_url";
                    leaf query_str {
                        type leafref {
                            path "../config/query_str";
                        }
                    }
                    leaf max_logs {
                        type leafref {
                            path "../config/max_logs";
                        }
                    }
                    leaf direction {
                        type leafref {
                            path "../config/direction";
                        }
                    }
                    leaf type {
                        type leafref {
                            path "../config/type";
                        }
                    }
                    leaf from_time {
                        type leafref {
                            path "../config/from_time";
                        }
                    }
                    leaf to_time {
                        type leafref {
                            path "../config/to_time";
                        }
                    }
                    leaf period {
                        type leafref {
                            path "../config/period";
                        }
                    }
                    leaf full_query {
                        type leafref {
                            path "../config/full_query";
                        }
                    }
                    leaf data_push_url {
                        type leafref {
                            path "../config/data_push_url";
                        }
                    }
                    container config {
                        uses config-type;
                    }
                } // list custom, this is used to set custom user defined queries

                container predefined {
                    leaf system_logs_vpn_and_dpd_15_min {
                        type leafref {
                            path "../config/query_str";
                        }
                    }
                    leaf system_log {
                        type leafref {
                            path "../config/query_str";
                        }
                    }
                    leaf percentage_of_traffic_that_is_one_way_or_asymmetric {
                        type leafref {
                            path "../config/query_str";
                        }
                    }
                    leaf raven_and_DNS_signature_threat_logs {
                        type leafref {
                            path "../config/query_str";
                        }
                    }
                    leaf PAN_DNS_related_logs {
                        type leafref {
                            path "../config/query_str";
                        }
                    }
                    leaf config_log {
                        type leafref {
                            path "../config/query_str";
                        }
                    }
                    leaf percentage_of_SaaS_applications_that_has_malware {
                        type leafref {
                            path "../config/query_str";
                        }
                    }
                    leaf URL_malware_blocks {
                        type leafref {
                            path "../config/query_str";
                        }
                    }
                    leaf URL_C2_blocks {
                        type leafref {
                            path "../config/query_str";
                        }
                    }
                    leaf URL_phishing_blocks {
                        type leafref {
                            path "../config/query_str";
                        }
                    }
                    leaf wildfire_detections {
                        type leafref {
                            path "../config/query_str";
                        }
                    }
                    leaf credential_theft {
                        type leafref {
                            path "../config/query_str";
                        }
                    }
                    leaf threats_permitted {
                        type leafref {
                            path "../config/query_str";
                        }
                    }
                    leaf system_logs_vpn_and_dpd_5_min {
                        type leafref {
                            path "../config/query_str";
                        }
                    }
                    leaf corr_object_events {
                        type leafref {
                            path "../config/query_str";
                        }
                    }
                    leaf corr_detailed_telemetry {
                        type leafref {
                            path "../config/query_str";
                        }
                    }
                    container config {
                        uses config-type;
                    }
                } // list predefined, this is used to run/get all predefined queries
            }
        }
    }
}
